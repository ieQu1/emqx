--------------------------------------------------------------------------
-- Copyright (c) 2025 EMQ Technologies Co., Ltd. All Rights Reserved.
--------------------------------------------------------------------------

-- Metadata definitions for emqx_ds_storage_reference module
DSBuiltinSLReference DEFINITIONS AUTOMATIC TAGS ::=
BEGIN
  IMPORTS TopicFilter FROM DSMetadataCommon;

  Stream ::= NULL

  ItStatic ::= SEQUENCE {
    topicFilter TopicFilter,
    startTime INTEGER
  }

  ItPos ::= SEQUENCE {
    pos OCTET STRING OPTIONAL
  }
END
