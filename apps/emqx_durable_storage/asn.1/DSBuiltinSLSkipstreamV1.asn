--------------------------------------------------------------------------
-- Copyright (c) 2025 EMQ Technologies Co., Ltd. All Rights Reserved.
--------------------------------------------------------------------------

--   emqx_ds_storage_skipstream_lts
DSBuiltinSLSkipstreamV1 DEFINITIONS AUTOMATIC TAGS ::=
BEGIN
  EXPORTS ALL;

  Stream ::= OCTET STRING

  IteratorStatic ::= SEQUENCE {
    static OCTET STRING,
    compressedTf OCTET STRING
  }
END
