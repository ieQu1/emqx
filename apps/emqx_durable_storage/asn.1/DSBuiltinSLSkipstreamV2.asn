--------------------------------------------------------------------------
-- Copyright (c) 2025 EMQ Technologies Co., Ltd. All Rights Reserved.
--------------------------------------------------------------------------

DSBuiltinSLSkipstreamV2 DEFINITIONS AUTOMATIC TAGS ::=
BEGIN
  IMPORTS TopicFilter FROM DSMetadataCommon;

  Stream ::= OCTET STRING

  IteratorStatic ::= SEQUENCE {
    static OCTET STRING,
    topicFilter TopicFilter
  }

  -- Iterator position is key that is already a binary
END
